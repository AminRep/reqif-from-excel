# NEEDS

# Specification: NEEDS
- ReqIF.Description: NEEDS demo specification.

## REQ-001: User login
The system shall allow a user to log in using a username and password.
- Priority: Medium
- Status: New
- Type: User Story

## REQ-002: Password policy
Passwords shall be at least 12 characters long and include letters and numbers.
- Priority: High
- Status: Planned
- Type: User Story
