# Capella Guide (ReqIFName/ReqIFText)

# Specification: Stakeholder Requirements
- ID: SR-001
- Description: Stakeholder requirements module.

## REQ-001: Make Audio Announcement (functional)
The Cabin Crew shall be able to make audio announcement.
- Status: Draft
- Priority: Medium

## REQ-002: PA System Interface (interface)
The system shall provide an interface to the PA amplifier.
- Status: Work-in-progress
- Priority: High
