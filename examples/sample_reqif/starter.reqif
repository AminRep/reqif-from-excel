# Starter ReqIF

# Specification: Stakeholder Requirements
- ID: SPEC-001

## REQ-001: User login
The system shall allow a user to log in using a username and password.
- Status: Draft
- Priority: Medium

## REQ-002: Password policy
Passwords shall be at least 12 characters long and include letters and numbers.
- Status: Approved
- Priority: High
