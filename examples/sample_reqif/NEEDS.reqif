# DEMO/NEEDS

# Specification: NEEDS
- ReqIF.Description: ReqView User Needs

## 45
© Copyright by Eccam s.r.o. All rights reserved.
- Type: Information

## 2: Introduction
- Type: Section

### 64: Purpose
- Type: Section

#### 67
The main purpose of this document is to provide new ReqView users a working example of a document describing high-level user needs by means of user stories.
- Type: Information

### 65: Scope
- Type: Section

#### 75
This document specifies top level user needs for a simple HW/SW requirements management tool.
Note: The document is not complete.
- Type: Information

#### 66
Users should be able to:
- Capture requirements specifications
- Manage requirements using custom attributes
- Set up requirements traceability
- Browse the requirements traceability matrix (RTM)
- Control project changes
- Filter and search requirements
- Import requirements from MS Word or Excel
- Export requirements to DOCX, XLSX, PDF, HTML, or CSV
- Analyze requirements coverage and impact of changes
- Print requirements specifications
- Integrate ReqView with Jira project management tool
- Integrate ReqView with Enterprise Architect modelling tool
- Type: Information

### 1: User Roles
- Type: Section

#### 5: Requirements Architect
Requirements Architect defines requirements model and configure the requirements project for other users.
Requirements Architect is typically a QA manager or project manager.
- As a(n): Architect
- I want to:
  - Define custom attributes
  - Configure project traceability
  - Create document templates
- Type: Information

#### 6: Editor
Editor defines project requirements and creates requirements and tests documents.
Editor is typically a requirements engineer, business analyst, project manager, QA engineer or a tester.
- I want to:
  - Capture structured requirements
  - Update requirements custom attributes
  - Discuss requirements
  - Maintain requirements traceability links
  - Print requirements
  - Import requirements
  - Export requirements
  - Create traceability reports
- Type: Information

#### 7: Reviewer
Reviewer reads project documents, performs review and provides feedback for improving the content of the document.
Reviewer is typically an internal QA expert reviewing requirements and tests, customer or supplier commenting requirements and setting the requirement acceptance state.
- I want to:
  - Provide feedback to requirements specifications
  - Update requirements review status
  - Print requirements
- Type: Information

## 3: User Stories
- Type: Section

### 9: Requirements Storage
- Type: Epic

#### 58: Document Files
- Acceptance Criteria: Tool supports:
  - saving project in a file
  - opening project from a file
- As a(n): Editor
- I want to: save document in a file
- So that: users can open the document for further editing or review
- Status: Implemented
- Type: User Story

#### 14: Document Templates
- Acceptance Criteria: Tool supports:
  - saving a document as a document template file,
  - add a new document into a project from a saved document template file while preserving document attributes definition, values of object attributes and object attachments.
- As a(n): Architect
- I want to: save a document as a template file
- So that: I can reuse the document structure and configuration of custom attributes for new documents
- Status: Implemented
- Type: User Story

#### 33: Autosave
- Acceptance Criteria: Tool:
  - instantly saves all the changes,
  - restores the same project content when it is restarted.
- As a(n): Editor
- I want to: automatically persist my changes
- So that: I do not lose my changes if the tool is unexpectedly terminated before saving into a file
- Status: Implemented
- Type: User Story

### 8: Define Requirements
- Type: Epic

#### 68: Requirement Description
- Acceptance Criteria: Tool supports:
  - setting a description of a selected requirement
  - removing description of a selected requirement
- As a(n): Editor
- I want to: specify requirements by a textual description
- So that: the requirements can be reviewed by other users.
- Status: Implemented
- Type: User Story

#### 32: Unique IDs
- Acceptance Criteria: Tool supports:
  - automatic generation of document ID which can not be further changed
- As a(n): Editor
- I want to: identify requirements by their unique ID
- So that: I can reference requirements from other documents or communication
- Status: Implemented
- Type: User Story

#### 12: Document Structure
- Acceptance Criteria: Tool supports:
  - creation of a new project,
  - adding a new document into a project,
  - deletion of a document from a project.
- As a(n): Editor
- I want to: organize requirements in a tree document hierarchy with numbered sections
- So that: I can easily navigate in the document structure
- Status: Implemented
- Type: User Story

#### 73: Table View
- Acceptance Criteria: Tool supports:
  - displaying of requirements in a table,
  - displaying requirements ID, description, discussion, links and custom attributes in columns,
  - hiding requirements table columns,
  - reordering of requirements table columns,
  - resizing of requirements table columns.
- As a(n): Editor
- I want to: display a table of requirements
- So that: I can review all requirements information in a single view
- Status: Implemented
- Type: User Story

#### 74: Detailed View
- Acceptance Criteria: Tool supports:
  - displaying custom attributes of the selected requirement in a pane or dialog,
  - displaying discussion of the selected requirement in a pane or dialog,
  - displaying traceability links for the selected requirement in a pane or dialog,
  - displaying history of changes for the selected requirement in a pane or dialog.
- As a(n): Editor
- I want to: display all information about the selected requirement
- So that: I can display details about any requirement which are not visible in the requirements table
- Status: Implemented
- Type: User Story

#### 17: Attachments
- Acceptance Criteria: Tool supports:
  - attachment of image file to document objects,
  - displaying image attachments in the context of the related document object,
  - deletion of attachments
- As a(n): Editor
- I want to: attach images and other documents to requirements
- So that: I can enhance textual requirements with visual content such as mockups, diagrams, etc.
- Status: Implemented
- Type: User Story

#### 35: Sort
- Acceptance Criteria: Tool supports sorting requirements by:
  - the natural document order,
  - value of a custom attribute.
- As a(n): Editor
- I want to: order requirements by a chosen custom attribute
- So that: I can display requirements sorted by priority, risk, effort, etc.
- Status: Planned
- Type: User Story

### 70: Manage Requirements
- Type: Epic

#### 19: Custom Attributes Configuration
- Acceptance Criteria: Tool supports:
  - creation of a new custom attribute,
  - deletion of a custom attribute,
  - definition of following custom attribute types
  - number
  - date
  - boolean
  - single and multivalue enumeration
  - string / rich formatted text
- As a(n): Architect
- I want to: define additional requirements attributes
- So that: the document can flexibly store additional requirement properties, such as requirement source, priority, status, etc.
- Status: Verified
- Type: User Story

#### 69: Custom Attributes
- Acceptance Criteria: Tool supports:
  - setting requirements source, priority, status and acceptance criteria
  - setting and resetting a value of a custom attribute for multiple requirements
- As a(n): Editor
- I want to: set a value of a chosen custom attribute for one or more selected requirements
- So that: I can define additional requirements properties, such as requirements source, prioritize requirements, manage requirement status, define acceptance criteria, etc.
- Status: Verified
- Type: User Story

#### 16: Traceability Configuration
- Acceptance Criteria: Tool supports:
  - creation of at least one link type
  - definition of a start and end role for a link type
  - removal of a link type including all existing links
- As a(n): Architect
- I want to: define types of relationships between requirements
- So that: users can perform traceability analysis for a chosen group of links
- Status: Implemented
- Type: User Story

#### 21: Traceability Links
- Acceptance Criteria: Tool supports:
  - creation of links with chosen link type between selected requirements,
  - deletion of links
- As a(n): Editor
- I want to: link related requirements
- So that: I can analyze requirements coverage, gap in requirements and impact of requirement changes.
- Status: Implemented
- Type: User Story

#### 34: Filter
- Acceptance Criteria: Tool supports filtering requirements:
  - by full text search in the object heading, text or a custom attribute
  - with the given traceability link type
  - in the given section
- As a(n): Editor
- I want to: filter requirements
- So that: I can identify and manipulate requirements matching a condition
- Status: Implemented
- Type: User Story

#### 36: Search
- Acceptance Criteria: Tool supports searching requirements containing a given keyword.
- As a(n): Editor
- I want to: find keywords
- So that: I can identify and manipulate requirements containing the searched keyword(s)
- Status: Implemented
- Type: User Story

### 22: Review Requirements
- Type: Epic

#### 24: Discussion
- Acceptance Criteria: Tool supports:
  - commenting a selected requirement,
  - displaying discussion for a selected requirement.
- As a(n): Reviewer
- I want to: comment requirements
- So that: I can provide feedback during requirements review
- Status: Implemented
- Type: User Story

#### 30: Traceability Browser
- Acceptance Criteria: Tool supports:
  - displaying linked requirements ordered by link type
  - changing focus to a selected requirement
  - filtering requirements with missing traceability links of a given link type
- As a(n): Reviewer
- I want to: trace related requirements
- So that: I can perform coverage, gap and change impact analysis
- Status: Implemented
- Type: User Story

#### 29: Print
- Acceptance Criteria: Tool supports:
  - printing a document with the same layout as it is displayed,
  - saving the document as PDF with the same layout as it is displayed.
- As a(n): Reviewer
- I want to: print a document view
- So that: I can review requirements without the need to run the tool
- Status: Implemented
- Type: User Story

### 31: Audit Trail
- Type: Epic

#### 26: History of Changes
- Acceptance Criteria: Tool supports:
  - displaying history of changes for a selected requirement.
- As a(n): Editor
- I want to: list all requirement changes
- So that: I can understand how the requirement evolved in time
- Status: Implemented
- Type: User Story

#### 23: Traceability Report
- Acceptance Criteria: Tool supports:
  - generation of a custom traceability report which visualizes end-to-end requirements traceability
- As a(n): Reviewer
- I want to: generate a traceability report
- So that: I can analyze coverage, gaps and impact of requirements changes
- Status: Implemented
- Type: User Story

### 11: Integrations
- Type: Epic

#### 27: Import from Word
- Acceptance Criteria: Tool supports:
  - import of MS Word HTML preserving structure of document sections and paragraphs and image attachments
  - pasting of a text or a HTML fragment to requirements description.
- As a(n): Editor
- I want to: import a requirements specification from a MS Word document
- So that: I can reuse existing requirements specifications or other structured documents
- Status: Implemented
- Type: User Story

#### 71: Import from Excel
- Acceptance Criteria: Tool supports:
  - import of new requirements from a CSV file including custom attribute values
  - updating requirements from a CSV file including custom attribute values
- As a(n): Editor
- I want to: import requirements from a MS Excel spreadsheet
- So that: I can import or update list of requirements
- Status: Implemented
- Type: User Story

#### 28: Export to Word
- Acceptance Criteria: Tool supports:
  - export of a document to a HTML file,
  - import of an exported HTML file to a MS Word document preserving requirements structure and content
- As a(n): Editor
- I want to: to export structured requirements specification to MS Word
- So that: I can share requirements specifications with users without the tool
- Status: Implemented
- Type: User Story

#### 72: Export to CSV
- Acceptance Criteria: Tool supports:
  - export of filtered list of requirements to a CSV file.
- As a(n): Editor
- I want to: export filtered list of requirements to MS Excel
- So that: I can reuse or update requirements in another application
- Status: Implemented
- Type: User Story

#### 80: Export to Jira
- Acceptance Criteria: Tool supports:
  - export of requirements from a document to Jira,
  - mapping type of requirements to Jira issue types,
  - setting Jira issue summary, description from ReqView id, heading and text attributes,
  - preserving values of other Jira issue fields updated by Jira users (iteration, owner, status),
  - preserving Jira links,
  - bidirectional navigation between exported ReqView requirements and corresponding Jira issues.
- As a(n): Editor
- I want to: export requirements to Jira
- So that: the development team can manage requirements implementation
- Status: Planned
- Type: User Story

#### 81: Update from Jira
- Acceptance Criteria: Tool supports:
  - mapping Jira issue fields to ReqView attributes,
  - updating values of mapped attributes from corresponding Jira issue fields.
- As a(n): Editor
- I want to: update requirements by information from Jira
- So that: I can track the implementation status in ReqView
- Status: Planned
- Type: User Story

#### 84: Export to ReqIF
- Acceptance Criteria: Tool supports:
  - exporting documents to the ReqIF format,
  - preserving requirements structure, format, attachments, attributes, and links between exported requirements,
  - compliance with OMG ReqIF standard.
- As a(n): Editor
- I want to: export document to the Requirements Interchange Format (ReqIF)
- So that: I can provide requirements in a standardized format to suppliers or other team members using other tools
- Status: Planned
- Type: User Story

#### 82: Export to Enterprise Architect
- Status: New
- Type: User Story

#### 83: Import from Enterprise Architect
- Status: New
- Type: User Story

## 4: Constraints
- Type: Section

### 39: Startup Time
- Acceptance Criteria: Tool starts in less than 10s even for large projects.
- As a(n): Editor
- I want to: quickly start the tool
- So that: I do not need to wait long time for editing a project
- Status: Verified
- Type: Constraint

### 41: Edit Response Time
- Acceptance Criteria: Tool updates view after any edit operation in a document with 10000 requirements in less than 1s.
- As a(n): Editor
- I want to: edit effectively requirements in large documents
- So that: I can work without waiting for tool responses
- Status: Verified
- Type: Constraint

### 44: Document Size
- Acceptance Criteria: Tool can store documents with 10000 requirements and 100 attachments of total size 100 MB.
- As a(n): Editor
- I want to: create large requirements specifications
- So that: I can capture all requirements in a single document even for complex system development projects
- Status: Verified
- Type: Constraint

### 42: Security
- Acceptance Criteria: Tool does not send any project information to the internet without user consent.
- As a(n): Editor
- I want to: store confidential information in the tool
- So that: I can be sure that no confidential information is compromised
- Status: Verified
- Type: Constraint

### 51: Compatibility
- Acceptance Criteria: Tool is installed and run on Windows, Linux and a Mac.
- As a(n): Editor
- I want to: install and run the tool on Windows, Linux or Mac operating system
- So that: I can use the tool on any desktop PC or notebook.
- Status: Verified
- Type: Constraint
