# Capella Guide (Pure Name/Text)

# Specification: Stakeholder Requirements
- ID: SR-001
- Description: Stakeholder requirements module.

## REQ-001: Make Audio Announcement (functional)
The Cabin Crew shall be able to make audio announcement.

## REQ-002: PA System Interface (interface)
The system shall provide an interface to the PA amplifier.
